;;; TEST HARNESS ONLY (never loaded by the tool).  Builds known-answer scenes with
;;; entmake in a DISPOSABLE scratch drawing (accoreconsole, discarded on exit),
;;; runs the read-only tool on them and writes JSON/CSV/TXT under an output root.
;;; No backslash characters (script transport halves them).
(vl-load-com)
(setq t:dirs '((1.0 0.0) (0.0 1.0) (-1.0 0.0) (0.0 -1.0)))   ; E N W S
(setq t:jb '(100.0 -50.0) t:tk 300.0 t:h 150.0 t:rail 20.0)  ; block-unit test geometry
(setq t:pi2 (/ pi 2.0))

(defun t:ensure-layer (name)
  (if (not (tblsearch "LAYER" name))
    (entmake (list '(0 . "LAYER") '(100 . "AcDbSymbolTableRecord") '(100 . "AcDbLayerTableRecord")
                   (cons 2 name) '(70 . 0) '(62 . 7) '(6 . "Continuous")))))
(defun t:reset (/ en nxt)
  (setq en (entnext))
  (while en (setq nxt (entnext en)) (entdel en) (setq en nxt)))
(defun t:rect (a b layer xd / x0 y0 x1 y1)
  (setq x0 (min (car a) (car b)) y0 (min (cadr a) (cadr b))
        x1 (max (car a) (car b)) y1 (max (cadr a) (cadr b)))
  (entmake (append
    (list '(0 . "LWPOLYLINE") '(100 . "AcDbEntity") (cons 8 layer) '(100 . "AcDbPolyline")
          '(90 . 4) '(70 . 1) (list 10 x0 y0) (list 10 x1 y0) (list 10 x1 y1) (list 10 x0 y1))
    (if xd (list (list -3 xd)) nil))))
(defun t:uv (o u ax cr)   ; point o + u*ax + n*cr, n = left normal of u
  (list (+ (car o) (* (car u) ax) (* (- (cadr u)) cr))
        (+ (cadr o) (* (cadr u) ax) (* (car u) cr))))
(defun t:type-arms (type)
  (cond ((= type "ELBOW") '(0 1)) ((= type "TEE") '(0 2 1)) (T '(0 1 2 3))))

;;; block: rails (two per arm) around joint t:jb, plus a circle and an arc as decoration
(defun t:def-fitting (name type / d u jx jy)
  (if (not (tblobjname "BLOCK" name))
    (progn
      (setq jx (car t:jb) jy (cadr t:jb))
      (entmake (list '(0 . "BLOCK") (cons 2 name) '(70 . 0) '(10 0.0 0.0 0.0)))
      (foreach d (t:type-arms type)
        (setq u (nth d t:dirs))
        (t:rect (t:uv t:jb u 0.0 (+ t:h (/ t:rail 2.0))) (t:uv t:jb u t:tk (- t:h (/ t:rail 2.0))) "0" nil)
        (t:rect (t:uv t:jb u 0.0 (- (+ t:h (/ t:rail 2.0)))) (t:uv t:jb u t:tk (+ (- t:h) (/ t:rail 2.0))) "0" nil))
      (entmake (list '(0 . "CIRCLE") '(8 . "0") (list 10 jx jy 0.0) '(40 . 10.0)))
      (entmake (list '(0 . "ARC") '(8 . "0") (list 10 jx jy 0.0) '(40 . 30.0) '(50 . 0.0) (cons 51 t:pi2)))
      (entmake '((0 . "ENDBLK"))))))

(defun t:path (pts profile width / xd)
  (regapp "CTR_PATH")
  (setq xd (if profile
             (list "CTR_PATH" '(1000 . "PATH") (cons 1040 (float width))
                   (cons 1000 (strcat "PROFILE=" profile)))
             nil))
  (entmake (append
    (list '(0 . "LWPOLYLINE") '(100 . "AcDbEntity") '(8 . "SCADA-TRAY-PATH") '(100 . "AcDbPolyline")
          (cons 90 (length pts)) '(70 . 0))
    (mapcar '(lambda (p) (list 10 (car p) (cadr p))) pts)
    (if xd (list (list -3 xd)) nil))))
(defun t:straight (j u a0 a1 w / rl)
  (regapp "CTR_GEN")
  (setq rl '("CTR_GEN" (1000 . "STRAIGHT")))
  (t:rect (t:uv j u a0 (+ (/ w 2.0) (/ t:rail 2.0))) (t:uv j u a1 (- (/ w 2.0) (/ t:rail 2.0))) "SCADA-TRAY" rl)
  (t:rect (t:uv j u a0 (- (+ (/ w 2.0) (/ t:rail 2.0)))) (t:uv j u a1 (+ (- (/ w 2.0)) (/ t:rail 2.0))) "SCADA-TRAY" rl)
  (t:rect (t:uv j u (+ a0 125.0) (- (/ w 2.0) (/ t:rail 2.0))) (t:uv j u (+ a0 165.0) (+ (- (/ w 2.0)) (/ t:rail 2.0))) "SCADA-TRAY" rl))
(defun t:insert (name ip rotq s type)
  (regapp "CTR_GEN")
  (entmake (list '(0 . "INSERT") '(100 . "AcDbEntity") '(8 . "SCADA-TRAY") '(100 . "AcDbBlockReference")
                 (cons 2 name) (list 10 (car ip) (cadr ip) 0.0)
                 (cons 41 s) (cons 42 s) (cons 43 s) (cons 50 (* rotq t:pi2))
                 (list -3 (list "CTR_GEN" (cons 1000 type))))))
(defun t:fit-ip (j rotq s shift / rot)   ; insert point that puts the block joint on j
  (setq rot (* rotq t:pi2))
  (list (+ (- (car j) (* s (- (* (car t:jb) (cos rot)) (* (cadr t:jb) (sin rot))))) (car shift))
        (+ (- (cadr j) (* s (+ (* (car t:jb) (sin rot)) (* (cadr t:jb) (cos rot))))) (cadr shift))))
(defun t:opt (key opts def) (if (assoc key opts) (cdr (assoc key opts)) def))

;;; correct (or deliberately faulty) Router-like junction.
;;;   opts: ("fitrot" . quarter-turns)  ("extra" . mm added to straight start)
;;;         ("shift" dx dy) ("width" . w) ("pprofile" . profile-or-nil)
(defun t:junction (blk type j k s opts / w pp fitrot extra shift d u kk)
  (setq w (t:opt "width" opts (* 300.0 s)) pp (t:opt "pprofile" opts nil)
        fitrot (t:opt "fitrot" opts k) extra (t:opt "extra" opts 0.0)
        shift (if (assoc "shift" opts) (cdr (assoc "shift" opts)) (list 0.0 0.0)))
  (t:ensure-layer "SCADA-TRAY-PATH") (t:ensure-layer "SCADA-TRAY")
  (foreach d (t:type-arms type)
    (setq kk (rem (+ d k) 4) u (nth kk t:dirs))
    (t:path (list j (list (+ (car j) (* 2500.0 (car u))) (+ (cadr j) (* 2500.0 (cadr u))))) pp w)
    (t:straight j u (+ (* t:tk s) extra) (+ (* t:tk s) extra 1000.0) w))
  (t:insert blk (t:fit-ip j fitrot s shift) fitrot s type)
  (setq t:last-insert (entlast)))

(defun t:defs ()
  (foreach b '(("SCADA_V2$SCADA_TRAY_ELBOW_V2" "ELBOW") ("SCADA_V2$SCADA_TRAY_TEE_V2" "TEE")
               ("SCADA_V2$SCADA_TRAY_CROSS_V2" "CROSS") ("SCADA_BASIC$SCADA_TRAY_ELBOW" "ELBOW")
               ("SCADA_BASIC$SCADA_TRAY_TEE" "TEE") ("SCADA_BASIC$SCADA_TRAY_CROSS" "CROSS")
               ("SCADA_TRAY_ELBOW" "ELBOW"))
    (t:def-fitting (car b) (cadr b))))

;;; ---- scenes: each returns the list of runs ---------------------------
(defun t:s-line-path ()
  (t:ensure-layer "SCADA-TRAY-PATH") (regapp "CTR_PATH")
  (entmake (list '(0 . "LINE") '(8 . "SCADA-TRAY-PATH") (list 10 10.0 20.0 5.0) (list 11 110.0 20.0 5.0)
    (list -3 (list "CTR_PATH" '(1000 . "PATH") (cons 1040 450.0) (cons 1000 "PROFILE=SCADA_V2")))))
  (list "export" "all"))
(defun t:s-lw-multi ()
  (t:ensure-layer "SCADA-TRAY-PATH")
  (t:path '((0.0 0.0) (100.0 0.0) (100.0 100.0) (200.0 100.0) (200.0 -50.0) (0.0 -50.0)) "SCADA_V2" 300.0)
  (entmake (list '(0 . "LWPOLYLINE") '(100 . "AcDbEntity") '(8 . "SCADA-TRAY-PATH") '(100 . "AcDbPolyline")
    '(90 . 4) '(70 . 1) '(10 500.0 500.0) '(42 . 0.5) '(10 600.0 500.0) '(10 600.0 600.0) '(10 500.0 600.0)))
  (list "export" "all"))
(defun t:s-elbow-r0 () (t:defs) (t:junction "SCADA_V2$SCADA_TRAY_ELBOW_V2" "ELBOW" '(1000.0 2000.0) 0 1.0 '(("pprofile" . "SCADA_V2"))) (list "all"))
(defun t:s-elbow-r1 () (t:defs) (t:junction "SCADA_V2$SCADA_TRAY_ELBOW_V2" "ELBOW" '(1000.0 2000.0) 1 0.5 '(("pprofile" . "SCADA_V2"))) (list "all"))
(defun t:s-elbow-r2 () (t:defs) (t:junction "SCADA_V2$SCADA_TRAY_ELBOW_V2" "ELBOW" '(1000.0 2000.0) 2 2.0 '(("pprofile" . "SCADA_V2"))) (list "all"))
(defun t:s-elbow-r3 () (t:defs) (t:junction "SCADA_V2$SCADA_TRAY_ELBOW_V2" "ELBOW" '(8766.7604 4929.3801) 3 0.4815924915 '(("pprofile" . "SCADA_V2"))) (list "all" (list "single" t:last-insert)))
(defun t:s-basic-elbow () (t:defs) (t:junction "SCADA_BASIC$SCADA_TRAY_ELBOW" "ELBOW" '(50.0 60.0) 1 1.3 '(("pprofile" . "SCADA_BASIC"))) (list "all"))
(defun t:s-tee-r0 () (t:defs) (t:junction "SCADA_V2$SCADA_TRAY_TEE_V2" "TEE" '(0.0 0.0) 0 0.945378 '(("pprofile" . "SCADA_V2"))) (list "all"))
(defun t:s-tee-r3 () (t:defs) (t:junction "SCADA_V2$SCADA_TRAY_TEE_V2" "TEE" '(0.0 0.0) 3 0.945378 '(("pprofile" . "SCADA_V2"))) (list "all"))
(defun t:s-cross () (t:defs) (t:junction "SCADA_V2$SCADA_TRAY_CROSS_V2" "CROSS" '(300.0 400.0) 0 0.945378 '(("pprofile" . "SCADA_V2"))) (list "all"))
(defun t:s-mixed-paths (/ j)
  (t:defs) (t:ensure-layer "SCADA-TRAY-PATH") (t:ensure-layer "SCADA-TRAY")
  (setq j '(0.0 0.0))
  ;; elbow with arms W (SCADA_V2 path) and S (SCADA_BASIC path); fitting is V2
  (t:path (list j '(-2500.0 0.0)) "SCADA_V2" 300.0)
  (t:path (list j '(0.0 -2500.0)) "SCADA_BASIC" 300.0)
  (t:straight j '(-1.0 0.0) t:tk (+ t:tk 1000.0) 300.0)
  (t:straight j '(0.0 -1.0) t:tk (+ t:tk 1000.0) 300.0)
  (t:insert "SCADA_V2$SCADA_TRAY_ELBOW_V2" (t:fit-ip j 2 1.0 '(0.0 0.0)) 2 1.0 "ELBOW")
  (list "all"))
(defun t:s-profile-mismatch () (t:defs)
  (t:junction "SCADA_V2$SCADA_TRAY_ELBOW_V2" "ELBOW" '(0.0 0.0) 0 1.0 '(("pprofile" . "SCADA_BASIC"))) (list "all"))
(defun t:s-no-xdata () (t:defs)
  (t:junction "SCADA_TRAY_ELBOW" "ELBOW" '(0.0 0.0) 1 1.0 '(("pprofile"))) (list "all"))
(defun t:s-no-path () (t:defs) (t:ensure-layer "SCADA-TRAY")
  (t:insert "SCADA_V2$SCADA_TRAY_ELBOW_V2" '(5000.0 5000.0) 0 1.0 "ELBOW") (list "all"))
(defun t:s-multi-candidates () (t:defs)
  (t:junction "SCADA_V2$SCADA_TRAY_ELBOW_V2" "ELBOW" '(0.0 0.0) 0 1.0 '(("pprofile" . "SCADA_V2")))
  (t:path '((-3000.0 400.0) (3000.0 400.0)) "SCADA_V2" 300.0)
  (t:path '((-3000.0 -900.0) (3000.0 -900.0)) "SCADA_V2" 300.0)
  (t:path '((7000.0 7000.0) (8000.0 7000.0)) "SCADA_BASIC" 300.0)
  (list "all"))
(defun t:s-escape () (t:defs)
  (t:junction "SCADA_V2$SCADA_TRAY_ELBOW_V2" "ELBOW" '(0.0 0.0) 0 1.0
    (list (cons "pprofile" (strcat "we" (chr 34) "ird,prof" (chr 92) "x " (chr 20013) (chr 25991)))))
  (list "all"))
(defun t:s-rot-error () (t:defs)
  (t:junction "SCADA_V2$SCADA_TRAY_ELBOW_V2" "ELBOW" '(0.0 0.0) 2 1.0 '(("pprofile" . "SCADA_V2") ("fitrot" . 1))) (list "all"))
(defun t:s-takeoff-error () (t:defs)
  (t:junction "SCADA_V2$SCADA_TRAY_ELBOW_V2" "ELBOW" '(0.0 0.0) 0 1.0 '(("pprofile" . "SCADA_V2") ("extra" . 5.0))) (list "all"))
(defun t:s-offset-error () (t:defs)
  (t:junction "SCADA_V2$SCADA_TRAY_ELBOW_V2" "ELBOW" '(0.0 0.0) 0 1.0 '(("pprofile" . "SCADA_V2") ("shift" 3.0 4.0))) (list "all"))
(defun t:s-no-fitting () (t:defs)
  (t:junction "SCADA_V2$SCADA_TRAY_ELBOW_V2" "ELBOW" '(0.0 0.0) 0 1.0 '(("pprofile" . "SCADA_V2")))
  (entdel t:last-insert)
  (list "all"))
(defun t:s-topology-mismatch () (t:defs)
  (t:junction "SCADA_V2$SCADA_TRAY_TEE_V2" "ELBOW" '(0.0 0.0) 0 1.0 '(("pprofile" . "SCADA_V2"))) (list "all"))
(defun t:s-readonly () (t:defs)
  (t:junction "SCADA_V2$SCADA_TRAY_CROSS_V2" "CROSS" '(0.0 0.0) 0 0.945378 '(("pprofile" . "SCADA_V2")))
  (list "all" "export" (list "single" t:last-insert)))

(defun t:s-unsupported-path-entity ()
  (t:ensure-layer "SCADA-TRAY-PATH")
  (entmake (list '(0 . "CIRCLE") '(8 . "SCADA-TRAY-PATH") (list 10 0.0 0.0 0.0) '(40 . 5.0)))
  (entmake (list '(0 . "ARC") '(8 . "SCADA-TRAY-PATH") (list 10 0.0 0.0 0.0) '(40 . 5.0) '(50 . 0.0) '(51 . 1.0)))
  (t:path '((0.0 0.0) (10.0 0.0)) "SCADA_V2" 300.0)
  (list "all"))
(defun t:s-extrusion-insert ()
  (t:defs) (t:ensure-layer "SCADA-TRAY") (regapp "CTR_GEN")
  (entmake (list '(0 . "INSERT") '(100 . "AcDbEntity") '(8 . "SCADA-TRAY") '(100 . "AcDbBlockReference")
                 (cons 2 "SCADA_V2$SCADA_TRAY_ELBOW_V2") (list 10 0.0 0.0 0.0) (list 210 0.0 0.0 -1.0)
                 (list -3 (list "CTR_GEN" (cons 1000 "ELBOW")))))
  (list "all"))
(defun t:s-xdata-tag-fitting ()
  ;; block name does NOT match any pattern; only the CTR_GEN tag says ELBOW
  (t:defs) (t:def-fitting "MY_CUSTOM_BEND" "ELBOW")
  (t:junction "MY_CUSTOM_BEND" "ELBOW" '(0.0 0.0) 0 1.0 '(("pprofile" . "DEFAULT")))
  (list "all"))
(defun t:s-future-profile ()
  ;; a profile / block naming that the tool has never heard of
  (t:def-fitting "SCADA_V9$SCADA_TRAY_ELBOW_V9" "ELBOW")
  (t:junction "SCADA_V9$SCADA_TRAY_ELBOW_V9" "ELBOW" '(0.0 0.0) 3 1.0 '(("pprofile" . "SCADA_V9")))
  (list "all"))
(defun t:s-not-a-fitting ()
  (t:def-fitting "DOOR_1" "ELBOW") (t:ensure-layer "SCADA-TRAY") (t:ensure-layer "0")
  (entmake (list '(0 . "INSERT") '(8 . "0") (cons 2 "DOOR_1") (list 10 5.0 5.0 0.0)))
  (list "all"))


;;; ---- CURVED elbow (40-LINE + ARC style like SCADA_TRAY_ELBOW_V2) -------------------------
;;; centre-line radius 576, rail centre-to-centre 622.9333, rail thickness 17.0667, stubs 68.2667 beyond the
;;; arc tangent points, radial rungs, a rung across each stub.  Native arms: W (at the 270-degree end of the
;;; arc) and N (at the 0-degree end).  Pivot (arc centre) is at (cx,cy) in block coordinates.
(setq t:cc 622.9333333333 t:ct 17.0666666667 t:cr 576.0 t:cst 68.2666666667)
(defun t:line (a b layer)
  (entmake (list '(0 . "LINE") (cons 8 layer) (list 10 (car a) (cadr a) 0.0) (list 11 (car b) (cadr b) 0.0))))
(defun t:def-curved (name cx cy decoy / ro1 ro2 ri1 ri2 r a)
  (if (not (tblobjname "BLOCK" name))
    (progn
      (setq ro1 (+ t:cr (/ t:cc 2.0) (/ t:ct 2.0)) ro2 (- ro1 t:ct)
            ri2 (- (- t:cr (/ t:cc 2.0)) (/ t:ct 2.0)) ri1 (+ ri2 t:ct))
      (entmake (list '(0 . "BLOCK") (cons 2 name) '(70 . 0) '(10 0.0 0.0 0.0)))
      (foreach r (list ro1 ro2 ri1 ri2)
        (entmake (list '(0 . "ARC") '(8 . "0") (list 10 cx cy 0.0) (cons 40 r) (cons 50 (* 1.5 pi)) '(51 . 0.0)))
        (t:line (list cx (- cy r)) (list (- cx t:cst) (- cy r)) "0")
        (t:line (list (+ cx r) cy) (list (+ cx r) (+ cy t:cst)) "0"))
      (t:line (list (- cx t:cst) (- cy ro1)) (list (- cx t:cst) (- cy ro2)) "0")
      (t:line (list (- cx t:cst) (- cy ri1)) (list (- cx t:cst) (- cy ri2)) "0")
      (t:line (list (+ cx ro1) (+ cy t:cst)) (list (+ cx ro2) (+ cy t:cst)) "0")
      (t:line (list (+ cx ri1) (+ cy t:cst)) (list (+ cx ri2) (+ cy t:cst)) "0")
      (t:line (list (- cx (/ t:cst 2.0)) (- cy ro2)) (list (- cx (/ t:cst 2.0)) (- cy ri1)) "0")
      (t:line (list (+ cx ro2) (+ cy (/ t:cst 2.0))) (list (+ cx ri1) (+ cy (/ t:cst 2.0))) "0")
      (foreach a (list (* 1.75 pi) (* 1.875 pi))
        (t:line (list (+ cx (* ri1 (cos a))) (+ cy (* ri1 (sin a)))) (list (+ cx (* ro2 (cos a))) (+ cy (* ro2 (sin a)))) "0"))
      (if decoy
        (t:line (list (- cx t:cst 400.0) (+ cy 700.0)) (list (- cx t:cst 400.0) (+ cy 800.0)) "0"))
      (entmake '((0 . "ENDBLK"))))))
(defun t:fit-ip2 (j rotq s shift jb / rot)
  (setq rot (* rotq t:pi2))
  (list (+ (- (car j) (* s (- (* (car jb) (cos rot)) (* (cadr jb) (sin rot))))) (car shift))
        (+ (- (cadr j) (* s (+ (* (car jb) (sin rot)) (* (cadr jb) (cos rot))))) (cadr shift))))
;;; curved elbow at junction j: native arms W,N rotated by k quarter turns.
;;;   opts: ("cx" . n) ("cy" . n) pivot in block coords  ("assumed" ("jb" x y)) place as if the joint were there
;;;         ("start" . mm-per-unit-scale-free takeoff override in block units)  ("fitrot" . q)
(defun t:curved-junction (blk j k s opts / cx cy jb w start kk1 kk2 u1 u2 fitrot)
  (setq cx (t:opt "cx" opts 0.0) cy (t:opt "cy" opts 0.0)
        jb (if (assoc "assumed" opts) (cdr (assoc "assumed" opts)) (list (+ cx t:cr) (- cy t:cr)))
        start (t:opt "start" opts (+ t:cr t:cst)) fitrot (t:opt "fitrot" opts k)
        w (* s t:cc))
  (t:ensure-layer "SCADA-TRAY-PATH") (t:ensure-layer "SCADA-TRAY")
  (foreach kk (list (rem (+ 2 k) 4) (rem (+ 1 k) 4))
    (setq u1 (nth kk t:dirs))
    (t:path (list j (list (+ (car j) (* 2500.0 (car u1))) (+ (cadr j) (* 2500.0 (cadr u1))))) "SCADA_V2" w)
    (t:straight j u1 (* start s) (+ (* start s) 1000.0) w))
  (t:insert blk (t:fit-ip2 j fitrot s (list 0.0 0.0) jb) fitrot s "ELBOW")
  (setq t:last-insert (entlast)))
(defun t:s-curved-r1 ()
  (t:def-curved "SCADA_V2$SCADA_TRAY_ELBOW_V2_CURVED_P0" 0.0 0.0 nil)
  (t:curved-junction "SCADA_V2$SCADA_TRAY_ELBOW_V2_CURVED_P0" '(1000.0 2000.0) 1 0.48159249 nil)
  (list "all"))
(defun t:s-curved-r3-shifted-pivot ()
  (t:def-curved "SCADA_V2$SCADA_TRAY_ELBOW_V2_CURVED_PS" -686.7333333333 521.0 nil)
  (t:curved-junction "SCADA_V2$SCADA_TRAY_ELBOW_V2_CURVED_PS" '(1000.0 2000.0) 3 0.48159249
                     (list (cons "cx" -686.7333333333) (cons "cy" 521.0)))
  (list "all"))
(defun t:s-curved-router-assumption ()
  ;; block drawn around a pivot that is NOT the origin, placed as if the pivot were the origin (joint at 576,-576)
  (t:def-curved "SCADA_V2$SCADA_TRAY_ELBOW_V2_CURVED_PS" -686.7333333333 521.0 nil)
  (t:curved-junction "SCADA_V2$SCADA_TRAY_ELBOW_V2_CURVED_PS" '(1000.0 2000.0) 1 0.48159249
                     (list (cons "assumed" (list 576.0 -576.0))))
  (list "all"))
(defun t:s-curved-takeoff-at-tangent ()
  ;; correct placement, Straights start at the arc tangent points (576) instead of the block openings (644.27)
  (t:def-curved "SCADA_V2$SCADA_TRAY_ELBOW_V2_CURVED_P0" 0.0 0.0 nil)
  (t:curved-junction "SCADA_V2$SCADA_TRAY_ELBOW_V2_CURVED_P0" '(1000.0 2000.0) 1 0.48159249 (list (cons "start" 576.0)))
  (list "all"))
(defun t:s-curved-decoy ()
  ;; a far protruding line outside the rails: the farthest point of the block is NOT an opening
  (t:def-curved "SCADA_V2$SCADA_TRAY_ELBOW_V2_CURVED_DECOY" 0.0 0.0 T)
  (t:curved-junction "SCADA_V2$SCADA_TRAY_ELBOW_V2_CURVED_DECOY" '(1000.0 2000.0) 1 0.48159249 nil)
  (list "all"))
(defun t:s-curved-rot-error ()
  (t:def-curved "SCADA_V2$SCADA_TRAY_ELBOW_V2_CURVED_P0" 0.0 0.0 nil)
  (t:curved-junction "SCADA_V2$SCADA_TRAY_ELBOW_V2_CURVED_P0" '(1000.0 2000.0) 1 0.48159249 (list (cons "fitrot" 2)))
  (list "all"))

;;; ---- blocks / scenes for: stacked (ambiguous) openings, no derivable openings, segment too short ----
(defun t:def-stacked (name / d u jx jy h2)
  ;; E+N elbow with TWO rail sets per arm (half widths 150 and 100) ending on the same cap line: like the V1 CROSS
  ;; block that stacks several variants on top of each other
  (if (not (tblobjname "BLOCK" name))
    (progn
      (setq jx (car t:jb) jy (cadr t:jb) h2 100.0)
      (entmake (list '(0 . "BLOCK") (cons 2 name) '(70 . 0) '(10 0.0 0.0 0.0)))
      (foreach d '(0 1)
        (setq u (nth d t:dirs))
        (foreach h (list t:h h2)
          (t:rect (t:uv t:jb u 0.0 (+ h (/ t:rail 2.0))) (t:uv t:jb u t:tk (- h (/ t:rail 2.0))) "0" nil)
          (t:rect (t:uv t:jb u 0.0 (- (+ h (/ t:rail 2.0)))) (t:uv t:jb u t:tk (+ (- h) (/ t:rail 2.0))) "0" nil)))
      (entmake '((0 . "ENDBLK"))))))
(defun t:def-nocaps (name / d u jx jy h)
  ;; E+N elbow drawn with open rail edges only (LINEs), no end caps -> no opening can be derived
  (if (not (tblobjname "BLOCK" name))
    (progn
      (setq jx (car t:jb) jy (cadr t:jb))
      (entmake (list '(0 . "BLOCK") (cons 2 name) '(70 . 0) '(10 0.0 0.0 0.0)))
      (foreach d '(0 1)
        (setq u (nth d t:dirs))
        (foreach cr (list (+ t:h 10.0) (- t:h 10.0) (- (- t:h 10.0)) (- (+ t:h 10.0)))
          (t:line (t:uv t:jb u 0.0 cr) (t:uv t:jb u t:tk cr) "0")))
      (entmake '((0 . "ENDBLK"))))))
(defun t:s-stacked-variants ()
  (t:def-stacked "SCADA_V2$SCADA_TRAY_ELBOW_V2_STACKED")
  (t:junction "SCADA_V2$SCADA_TRAY_ELBOW_V2_STACKED" "ELBOW" '(0.0 0.0) 0 1.0 '(("pprofile" . "SCADA_V2")))
  (list "all"))
(defun t:s-stacked-unpaired ()
  (t:def-stacked-x "SCADA_V2$SCADA_TRAY_ELBOW_V2_STACKEDX")
  (t:junction "SCADA_V2$SCADA_TRAY_ELBOW_V2_STACKEDX" "ELBOW" '(0.0 0.0) 0 1.0 '(("pprofile" . "SCADA_V2")))
  (list "all"))
(defun t:def-stacked-x (name / d u jx jy h2)
  (if (not (tblobjname "BLOCK" name))
    (progn
      (setq jx (car t:jb) jy (cadr t:jb) h2 100.0)
      (entmake (list '(0 . "BLOCK") (cons 2 name) '(70 . 0) '(10 0.0 0.0 0.0)))
      (foreach d '(0 1)
        (setq u (nth d t:dirs))
        (foreach h (list t:h h2)
          (t:rect (t:uv t:jb u 0.0 (+ h (/ t:rail 2.0))) (t:uv t:jb u t:tk (- h (/ t:rail 2.0))) "0" nil)
          (t:rect (t:uv t:jb u 0.0 (- (+ h (/ t:rail 2.0)))) (t:uv t:jb u t:tk (+ (- h) (/ t:rail 2.0))) "0" nil)))
      ;; extra clean arm facing S
      (setq u (nth 3 t:dirs))
      (t:rect (t:uv t:jb u 0.0 (+ t:h (/ t:rail 2.0))) (t:uv t:jb u t:tk (- t:h (/ t:rail 2.0))) "0" nil)
      (t:rect (t:uv t:jb u 0.0 (- (+ t:h (/ t:rail 2.0)))) (t:uv t:jb u t:tk (+ (- t:h) (/ t:rail 2.0))) "0" nil)
      (entmake '((0 . "ENDBLK"))))))
(defun t:s-no-caps ()
  (t:def-nocaps "SCADA_V2$SCADA_TRAY_ELBOW_V2_NOCAPS")
  (t:junction "SCADA_V2$SCADA_TRAY_ELBOW_V2_NOCAPS" "ELBOW" '(0.0 0.0) 0 1.0 '(("pprofile" . "SCADA_V2")))
  (list "all"))
(defun t:s-short-segment (/ j1 j2 e)
  ;; two Elbows 500 apart; each needs 300 -> no Straight fits between them (the Router would not generate one)
  (t:defs) (t:ensure-layer "SCADA-TRAY-PATH") (t:ensure-layer "SCADA-TRAY")
  (setq j1 '(0.0 0.0) j2 '(0.0 500.0) e '(1.0 0.0))
  (t:path (list j1 '(2500.0 0.0)) "SCADA_V2" 300.0)
  (t:path (list j1 j2) "SCADA_V2" 300.0)
  (t:path (list j2 '(2500.0 500.0)) "SCADA_V2" 300.0)
  (t:straight j1 e 300.0 1300.0 300.0)
  (t:straight j2 e 300.0 1300.0 300.0)
  (t:insert "SCADA_V2$SCADA_TRAY_ELBOW_V2" (t:fit-ip j1 0 1.0 '(0.0 0.0)) 0 1.0 "ELBOW")
  (t:insert "SCADA_V2$SCADA_TRAY_ELBOW_V2" (t:fit-ip j2 3 1.0 '(0.0 0.0)) 3 1.0 "ELBOW")
  (list "all"))

;;; ---- driver -----------------------------------------------------------
(defun t:dump (path / f en tn tab)
  (setq f (open path "w" "utf8"))
  (princ (strcat "HANDSEED=" (vl-princ-to-string (getvar "HANDSEED")) (chr 10)) f)
  (setq en (entnext))
  (while en (princ (strcat (vl-princ-to-string (entget en '("*"))) (chr 10)) f) (setq en (entnext en)))
  (foreach tab '("LAYER" "BLOCK" "APPID" "LTYPE" "STYLE" "DIMSTYLE" "VIEW" "UCS")
    (setq tn (tblnext tab T))
    (while tn (princ (strcat tab ":" (vl-princ-to-string tn) (chr 10)) f) (setq tn (tblnext tab))))
  (close f))
(defun t:run-scene (name root / runs r res spec msg)
  (t:reset)
  (setq t:last-insert nil)
  (setq res (vl-catch-all-apply (read (strcat "t:s-" name)) nil))
  (if (vl-catch-all-error-p res)
    (princ (strcat (chr 10) "SCENE_ERROR " name " " (vl-catch-all-error-message res)))
    (progn
      (setq runs res)
      (t:dump (strcat root name "_before.txt"))
      (foreach r runs
        (setq spec (if (listp r) (car r) r))
        (setq ard:out-dir (strcat root name "/" spec "/"))
        (setq msg (vl-catch-all-apply 'ard:run (list spec (if (listp r) (cadr r) nil))))
        (if (vl-catch-all-error-p msg)
          (princ (strcat (chr 10) "RUN_ERROR " name " " spec " " (vl-catch-all-error-message msg)))))
      (t:dump (strcat root name "_after.txt"))
      (princ (strcat (chr 10) "SCENE_DONE " name)))))
(princ)
